/*
 * SYS5100Lib: the SYS 5100 course metadata library (binding names: docs/INTERFACES.md).
 * Import it in your model with:   private import SYS5100Lib::*;
 * Do not edit this file in your team repository; the checks rely on these names.
 */
package SYS5100Lib {
  private import ScalarValues::*;
  enum def Basis { specified; measured; calculated; estimated; assumed; predicted; }
  metadata def Evidence { attribute grade : Basis; attribute source : String; }   // source = INT-/OBS-/DOC-/HYP- id or document
  metadata def Budget   { attribute basis : Basis; attribute growth : Real; }       // growth allowance fraction, e.g. 0.20
  metadata def RiskLink { attribute riskId : String; attribute threat : String; }
  metadata def TestVerdict { attribute verdict : VerificationCases::VerdictKind;    // pass | fail | inconclusive | error
                             attribute asRun : String; attribute ncr : String; }   // ncr = "none" or NCR id
  enum def CRStatus { proposed; approved; rejected; deferred; implemented; }
  metadata def Baseline { attribute tag : String; }
  metadata def ChangeRecord { attribute crId : String; attribute status : CRStatus; attribute decidedBy : String; }
}
